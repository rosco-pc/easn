--ASN.1 Formal Description
--SDP output CDR specification version 4.3

SDPOUTPUTCDR {iso(1) member-body(2) bsi(826)
disc(0) ericsson(1249) mobileDomain(0) charging(5)
sDPOUTPUTCDR(1) asn1Module(0)}

DEFINITIONS IMPLICIT TAGS ::=

BEGIN

SDPCallDataRecord ::= CHOICE {
   cDRProcessed                 [1] CDRProcessed,
   accountAdjustment            [2] AccountAdjustment,
   negativeBalance              [3] NegativeBalance,
   bonusAdjustment              [4] BonusAdjustment,
   serviceFeeDeduction          [5] ServiceFeeDeduction,
   lifeCycleChange              [6] LifeCycleChange,
   negativeBalanceBarred        [7] NegativeBalanceBarred,
   valueVoucherExpiry           [8] ValueVoucherExpiry,
   periodicAdjustment           [9] PeriodicAdjustment,
   periodicReset                [10] PeriodicReset,
   temporaryBlock               [11] TemporaryBlock
}

CDRProcessed ::= SEQUENCE {
   recordType                   [1] RecordType,
   sdpID                        [2] NodeID,
   cdrID                        [3] RecordSequenceNumberString,
   originalCdrNodeID            [4] NodeID OPTIONAL,
   originalCdrID                [5] RecordSequenceNumberString
                                    OPTIONAL,
   subscriberNumber             [6] SubscriberNumberString,
   relatedNumber                [7] RelatedNumberString,
   originalCdrTimeStamp         [8] TimeStamp OPTIONAL,
   cDRProcessingTimeStamp       [9] TimeStamp,
   balanceBeforeCDRProc         [10] MoneyAmount,
   balanceAfterCDRProc          [11] MoneyAmount,
   eventCost                    [12] MoneyAmount,
   surplusDebit                 [13] MoneyAmount OPTIONAL,
   familyAndFriendsIndicator    [14] FamilyAndFriendsIndicator
                                     OPTIONAL,
   serviceClassId               [15] ServiceClass,
   currencyType                 [16] CurrencyType,
   tempBlocked                  [17] BOOLEAN OPTIONAL,
   accountNumber                [18] NumberString OPTIONAL,
   accountGroupID               [19] AccountGroupID OPTIONAL,
   serviceOfferings             [20] ServiceOfferings OPTIONAL,
   selectedCommunityIndicator   [21] SelectedCommunityIndicator
                                     OPTIONAL,
   communityID1Charged          [22] CommunityID OPTIONAL,
   communityID2Charged          [23] CommunityID OPTIONAL,
   communityID3Charged          [24] CommunityID OPTIONAL,
   communityID1NonCharged       [25] CommunityID OPTIONAL,
   communityID2NonCharged       [26] CommunityID OPTIONAL,
   communityID3NonCharged       [27] CommunityID OPTIONAL,
   communityDataNonChargedNotAvailable
                                [28] BOOLEAN OPTIONAL,
   subscriberConvergent         [29] BOOLEAN OPTIONAL,
   updatedAccumulatorID         [30] AccumulatorID OPTIONAL,
   cdrProcDedicatedAccounts     [31] SEQUENCE (SIZE (1..255)) OF
                                     CDRProcDedicatedAccount
                                     OPTIONAL,
   cdrProcAccumulators          [32] SEQUENCE (SIZE (1..255)) OF
                                     CDRProcAccumulator
                                     OPTIONAL,
   categorizationInformation    [33] CategorizationInformation
                                     OPTIONAL,
   ratedDurations               [34] RatedDurations OPTIONAL,
   individualPriceFactorHistory [35] SEQUENCE OF 
                                     IndividualPriceFactorHistory OPTIONAL,
  ...
}

AccountAdjustment ::= SEQUENCE {
   adjustmentRecordType         [1] AdjustmentRecordType,
   sdpID                        [2] NodeID,
   cdrID                        [3] RecordSequenceNumberString,
   accountNumber                [4] NumberString,
   subscriberNumber             [5] NumberString,
   adjustmentTimeStamp          [6] TimeStamp,
   adjustmentAction             [7] AdjustmentAction OPTIONAL,
   balanceBefore                [8] MoneyAmount OPTIONAL,
   balanceAfter                 [9] MoneyAmount OPTIONAL,
   adjustmentAmount             [10] MoneyAmount OPTIONAL,
   serviceClassId               [11] ServiceClass,
   currencyType                 [12] CurrencyType,
   originalAdjustmentAmount     [13] MoneyAmount OPTIONAL,
   originalCurrencyType         [14] CurrencyType OPTIONAL,
   originNodeType               [15] NodeType OPTIONAL,
   originNodeId                 [16] IDString OPTIONAL,
   origTransactionID            [17] TransactionID OPTIONAL,
   origTransactionTimeStamp     [18] TimeStamp OPTIONAL,
   transactionType              [19] TransactionType OPTIONAL,
   transactionCode              [20] TransactionCode OPTIONAL,
   originOperatorId             [21] IDString OPTIONAL,
   supervisionExpDateBefore     [22] Date OPTIONAL,
   supervisionExpDateAfter      [23] Date OPTIONAL,
   creditClearancePeriodBefore  [24] Period OPTIONAL,
   creditClearancePeriodAfter   [25] Period OPTIONAL,
   servFeeExpDateBefore         [26] Date OPTIONAL,
   servFeeExpDateAfter          [27] Date OPTIONAL,
   serviceRemovalPeriodBefore   [28] Period OPTIONAL,
   serviceRemovalPeriodAfter    [29] Period OPTIONAL,
   accountFlagsBefore           [30] AccountFlags OPTIONAL,
   accountFlagsAfter            [31] AccountFlags OPTIONAL,
   newServiceClass              [32] ServiceClass OPTIONAL,
   valueVoucherExpDateBefore    [33] Date OPTIONAL,
   valueVoucherExpDateAfter     [34] Date OPTIONAL,
   temporaryServiceClassBefore  [35] ServiceClass OPTIONAL,
   temporaryServiceClassAfter   [36] ServiceClass OPTIONAL,
   activationDate               [37] Date OPTIONAL,
   refillUnbarTimeStamp         [38] TimeStamp OPTIONAL,
   oldLanguage                  [39] Language OPTIONAL,
   newLanguage                  [40] Language OPTIONAL,
   promotionPlanIDBefore        [41] PromotionPlan OPTIONAL,
   promotionPlanIDAfter         [42] PromotionPlan OPTIONAL,
   negativeBalanceBarringDate   [43] Date OPTIONAL,
   oldAccountGroupID            [44] AccountGroupID OPTIONAL,
   oldServiceOfferings          [45] ServiceOfferings OPTIONAL,
   oldCommunityID1              [46] CommunityID OPTIONAL,
   oldCommunityID2              [47] CommunityID OPTIONAL,
   oldCommunityID3              [48] CommunityID OPTIONAL,
   newAccountGroupID            [49] AccountGroupID OPTIONAL,
   newServiceOfferings          [50] ServiceOfferings OPTIONAL,
   subscriberConvergent         [51] BOOLEAN OPTIONAL,
   newCommunityID1              [52] CommunityID OPTIONAL,
   newCommunityID2              [53] CommunityID OPTIONAL,
   newCommunityID3              [54] CommunityID OPTIONAL,
   counterTypeID                [55] INTEGER OPTIONAL,
   totalCounterStartValue       [56] CounterValue OPTIONAL,
   totalCounterDeltaValue       [57] CounterDelta OPTIONAL,
   periodCounterStartValue      [58] CounterValue OPTIONAL,
   periodCounterDeltaValue      [59] CounterDelta OPTIONAL,
   deductedAmount               [60] MoneyAmount OPTIONAL,
   cost                         [61] MoneyAmount OPTIONAL,
   costService                  [62] MoneyAmount OPTIONAL,
   presentedCost                [63] MoneyAmount OPTIONAL,
   chargingSuccessCode          [64] ChargingSuccessCode
                                     OPTIONAL,
   chargingIndicator            [65] INTEGER OPTIONAL,
   familyAndFriendsAction       [66] FamilyAndFriendsAction
                                     OPTIONAL,
   familyAndFriendsNumber       [67] NumberString OPTIONAL,
   familyAndFriendsIndicator    [68] FamilyAndFriendsIndicator
                                     OPTIONAL,
   owner                        [69] Owner OPTIONAL,
   accountHomeRegion            [70] AccountHomeRegion OPTIONAL,
   changedPIN                   [71] BOOLEAN OPTIONAL,
   accountUnbarSuppressed       [72] BOOLEAN OPTIONAL,
   adjustmentDedicatedAccounts  [73] SEQUENCE (SIZE (1..255)) OF
                                     AdjustmentDedicatedAccount
                                     OPTIONAL,
   adjustmentAccumulators       [74] SEQUENCE (SIZE (1..255)) OF
                                     AdjustmentAccumulator
                                     OPTIONAL,
   origServiceClassBefore       [75] ServiceClass OPTIONAL,
   origServiceClassAfter        [76] ServiceClass OPTIONAL,
   serviceSessionID             [77] UTF8String OPTIONAL,
   duplicatingCDRNode           [78] NodeType OPTIONAL,
   -- PC
   aggregatedBalanceBefore      [79] MoneyAmount OPTIONAL,
   aggregatedBalanceAfter       [80] MoneyAmount OPTIONAL,
   adjustmentFaFs               [81] SEQUENCE OF
                                     AdjustmentFaF
                                     OPTIONAL,
   adjustmentOffers             [82] SEQUENCE OF
                                     AdjustmentOffer
                                     OPTIONAL,
   -- PC end
   lastRecord                   [83] BOOLEAN OPTIONAL,
   ...
}

NegativeBalance ::= SEQUENCE {
   accountNumber                [1] NumberString,
   accountBalanceBefore         [2] MoneyAmount,
   accountBalanceAfter          [3] MoneyAmount,
   timeStamp                    [4] TimeStamp,
   sdpID                        [5] NodeID OPTIONAL,
   cdrID                        [6] RecordSequenceNumberString
                                    OPTIONAL,
   subscriberConvergent         [7] BOOLEAN OPTIONAL,
   -- PC
   aggregatedBalanceBefore      [8] MoneyAmount OPTIONAL,
   aggregatedBalanceAfter       [9] MoneyAmount OPTIONAL,
   aggregatedBalanceDedicatedAccounts
                                [10] SEQUENCE (SIZE (1..255)) OF
                                     AggregatedBalanceDedicatedAccount
                                     OPTIONAL,
   -- PC end
   ...
}

BonusAdjustment ::= SEQUENCE {
   sdpID                        [1] NodeID,
   cdrID                        [2] RecordSequenceNumberString,
   accountNumber                [3] NumberString,
   subscriberNumber             [4] NumberString,
   bonusTimeStamp               [5] TimeStamp,
   currencyType                 [6] CurrencyType,
   serviceClassId               [7] ServiceClass,
   accountBalanceBeforeBonus    [8] MoneyAmount OPTIONAL,
   accountBalanceAfterBonus     [9] MoneyAmount OPTIONAL,
   bonusAmount                  [10] MoneyAmount OPTIONAL,
   subscriberConvergent         [11] BOOLEAN OPTIONAL,
   accountGroupID               [12] AccountGroupID OPTIONAL,
   serviceOfferings             [13] ServiceOfferings OPTIONAL,
   bonusDedicatedAccounts       [14] SEQUENCE (SIZE (1..255)) OF
                                     BonusDedicatedAccount
                                     OPTIONAL,
   bonusAccumulators            [15] SEQUENCE (SIZE (1..255)) OF
                                     BonusAccumulator
                                     OPTIONAL,
   lifeCycleInformation         [16] LifeCycleInformation OPTIONAL,
   ...
}

ServiceFeeDeduction ::= SEQUENCE {
   sdpID                        [1] NodeID,
   cdrID                        [2] RecordSequenceNumberString,
   originNodeType               [3] NodeType,
   timeStamp                    [4] TimeStamp,
   accountNumber                [5] NumberString,
   serviceFeeAmount             [6] MoneyAmount,
   successCode                  [7] ServFeeDeductSuccessCode,
   oldServiceClass              [8] ServiceClass,
   newServiceClass              [9] ServiceClass OPTIONAL,
   currencyType                 [10] CurrencyType,
   servFeeExpDateBefore         [11] Date OPTIONAL,
   servFeeExpDateAfter          [12] Date OPTIONAL,
   accountFlags                 [13] AccountFlags,
   negativeBalanceBarringDate   [14] Date OPTIONAL,
   balanceAfterDeduction        [15] MoneyAmount,
   lastRecord                   [16] BOOLEAN OPTIONAL,
   accountGroupID               [17] AccountGroupID OPTIONAL,
   subscriberConvergent         [18] BOOLEAN OPTIONAL,
   subscriberNumber             [19] NumberString OPTIONAL,
   serviceFeeType               [20] ServiceFeeType OPTIONAL,
   debt                         [21] MoneyAmount OPTIONAL,
   subscriberFee                [22] MoneyAmount OPTIONAL,
   clearedDedicatedAccounts     [23] SEQUENCE (SIZE (1..255)) OF
                                     ClearedDedicatedAccount
                                     OPTIONAL,
   clearedAccumulators          [24] SEQUENCE (SIZE (1..255)) OF
                                     ClearedAccumulator
                                     OPTIONAL,
   -- PC
   aggregatedBalanceBefore      [25] MoneyAmount OPTIONAL,
   aggregatedBalanceAfter       [26] MoneyAmount OPTIONAL,
   aggregatedBalanceDedicatedAccounts  
                                [27] SEQUENCE (SIZE (1..255)) OF
                                     AggregatedBalanceDedicatedAccount
                                     OPTIONAL,
   removedFaFs                  [28] SEQUENCE OF
                                     RemovedFaF
                                     OPTIONAL,
   removedOffers                [29] SEQUENCE OF
                                     RemovedOffer
                                     OPTIONAL,
   -- PC end
   -- PC:06912
   ignoredDebt                  [30] MoneyAmount OPTIONAL,
   -- PC end
   ...
 }

LifeCycleChange ::= SEQUENCE {
   sdpID                        [1] NodeID,
   cdrID                        [2] RecordSequenceNumberString,
   originNodeType               [3] NodeType,
   timeStamp                    [4] TimeStamp,
   accountNumber                [5] NumberString,
   subscriberNumber             [6] NumberString,
   serviceClassId               [7] ServiceClass, 
   language                     [8] Language OPTIONAL,
   currencyType                 [9] CurrencyType,
   initialAmountAdded           [10] MoneyAmount OPTIONAL,
   initialSupervisionExpDate    [11] Date OPTIONAL,
   initialServiceFeeExpDate     [12] Date OPTIONAL,
   supervisionExpDate           [13] Date OPTIONAL,
   creditClearancePeriod        [14] Period OPTIONAL,
   servFeeExpDate               [15] Date OPTIONAL,
   serviceRemovalPeriod         [16] Period OPTIONAL,
   clearedAccountValue          [17] MoneyAmount OPTIONAL,
   accountFlagsBefore           [18] AccountFlags,
   accountFlagsAfter            [19] AccountFlags,
   activationDate               [20] Date OPTIONAL,
   refillUnbarTimeStamp         [21] TimeStamp OPTIONAL,
   iVRWelcomeStatus             [22] BOOLEAN OPTIONAL,
   negativeBalanceBarringDate   [23] Date OPTIONAL,
   promotionPlanID              [24] PromotionPlan OPTIONAL,
   promotionPlanStartDate       [25] Date OPTIONAL,
   promotionPlanEndDate         [26] Date OPTIONAL,
   accumulatedRefillCounter     [27] INTEGER OPTIONAL,
   accumulatedRefillValue       [28] MoneyAmount OPTIONAL,
   accumulatedProgressionCounter
                                [29] INTEGER OPTIONAL,
   accumulatedProgressionValue  [30] MoneyAmount OPTIONAL,
   preActReasonCode             [31] PreActReasonCode 
                                     OPTIONAL,
   creditCleared                [32] BOOLEAN OPTIONAL,
   serviceExpired               [33] BOOLEAN OPTIONAL,
   originOperatorId             [34] IDString OPTIONAL,
   originNodeId                 [35] IDString,
   origTransactionID            [36] TransactionID OPTIONAL,
   origTransactionTimeStamp     [37] TimeStamp OPTIONAL,
   lastRecord                   [38] BOOLEAN OPTIONAL,
   accountGroupID               [39] AccountGroupID OPTIONAL,
   serviceOfferings             [40] ServiceOfferings OPTIONAL,
   communityID1                 [41] CommunityID OPTIONAL,
   communityID2                 [42] CommunityID OPTIONAL,
   communityID3                 [43] CommunityID OPTIONAL,
   subscriberConvergent         [44] BOOLEAN OPTIONAL,
   initialCreditClearanceGracePeriod
                                [45] Period OPTIONAL,
   initialServiceRemovalGracePeriod
                                [46] Period OPTIONAL,
   subscriberCreated            [47] BOOLEAN OPTIONAL,
   subscriberDeleted            [48] BOOLEAN OPTIONAL,
   accountHomeRegion            [49] AccountHomeRegion OPTIONAL,
   disconnectionCode            [50] DisconnectionCode OPTIONAL,
   clearedDedicatedAccounts     [51] SEQUENCE (SIZE (1..255)) OF
                                     ClearedDedicatedAccount
                                     OPTIONAL,
   creditClearedReasonMainAccount
                                [52] Reason OPTIONAL,
   -- PC
   clearedAggregatedValue       [53] MoneyAmount OPTIONAL,
   removedFaFs                  [54] SEQUENCE OF
                                     RemovedFaF
                                     OPTIONAL,
   removedOffers                [55] SEQUENCE OF
                                     RemovedOffer
                                     OPTIONAL,
   -- PC end
   ...
}

NegativeBalanceBarred ::= SEQUENCE {
   sdpID                        [1] NodeID,
   cdrID                        [2] RecordSequenceNumberString,
   accountNumber                [3] NumberString,
   timeStamp                    [4] TimeStamp,
   accountBalance               [5] MoneyAmount,
   currencyType                 [6] CurrencyType,
   lastRecord                   [7] BOOLEAN OPTIONAL,
   subscriberConvergent         [8] BOOLEAN OPTIONAL,
   -- PC
   aggregatedBalance            [9] MoneyAmount OPTIONAL,
   -- PC end
   ...
}

ValueVoucherExpiry ::= SEQUENCE {
   sdpID                        [1] NodeID,
   cdrID                        [2] RecordSequenceNumberString,
   accountNumber                [3] NumberString,
   timeStamp                    [4] TimeStamp,
   accountFlagsBefore           [5] AccountFlags OPTIONAL,
   accountFlagsAfter            [6] AccountFlags OPTIONAL,
   oldServiceClass              [7] ServiceClass,
   newServiceClass              [8] ServiceClass,
   negativeBalanceBarringDate   [9] Date OPTIONAL,
   currencyType                 [10] CurrencyType,
   valueVoucherExpDate          [11] Date,
   lastRecord                   [12] BOOLEAN OPTIONAL,
   subscriberConvergent         [13] BOOLEAN OPTIONAL,
   clearedDedicatedAccounts     [14] SEQUENCE (SIZE (1..255)) OF
                                     ClearedDedicatedAccount
                                     OPTIONAL,
   clearedAccumulators          [15] SEQUENCE (SIZE (1..255)) OF
                                     ClearedAccumulator
                                     OPTIONAL,
   -- PC
   aggregatedBalanceBefore      [16] MoneyAmount OPTIONAL,
   aggregatedBalanceAfter       [17] MoneyAmount OPTIONAL,
   removedFaFs                  [18] SEQUENCE OF
                                     RemovedFaF
                                     OPTIONAL,
   removedOffers                [19] SEQUENCE OF
                                     RemovedOffer
                                     OPTIONAL,
   -- PC end
   ...
}

PeriodicAdjustment ::= SEQUENCE {
   sdpID                        [1] NodeID,
   cdrID                        [2] RecordSequenceNumberString,
   timeStamp                    [3] TimeStamp,
   accountNumber                [4] NumberString,
   dedicatedAccountID           [5] DedicatedAccountID,
   currencyType                 [6] CurrencyType,
   lastRecord                   [7] BOOLEAN OPTIONAL,
   replenishmentID              [8] ReplenishmentID,
   rolloverNewPeriod            [9] MoneyAmount OPTIONAL,
   rolloverOldPeriod            [10] MoneyAmount OPTIONAL,
   replenishmentDate            [11] Date OPTIONAL,
   replenishmentAmount          [12] MoneyAmount OPTIONAL,
   oldReplenishmentAmount       [13] MoneyAmount OPTIONAL,
   balanceBeforeAdjustment      [14] MoneyAmount OPTIONAL,
   unusedRollover               [15] MoneyAmount OPTIONAL,
   oldServiceClass              [16] ServiceClass OPTIONAL,
   serviceClassId               [17] ServiceClass,
   dedicatedAccountAdjustment   [18] MoneyAmount OPTIONAL,
   dedicatedAccountClearance    [19] MoneyAmount OPTIONAL,
   rolloverCalculationApplied   [20] BOOLEAN OPTIONAL,
   periodOffset                 [21] INTEGER OPTIONAL,
   startDate                    [22] Date OPTIONAL,
   periodLength                 [23] INTEGER OPTIONAL,
   typeOfPeriod                 [24] PeriodType OPTIONAL,
   -- PC
   aggrBalBeforeAdjustment      [25] MoneyAmount OPTIONAL,
   dedicatedAccountRealMoney    [26] BOOLEAN OPTIONAL,
   offerID                      [27] OfferID OPTIONAL,
   accountUnitType              [28] AccountUnitType OPTIONAL,
   -- PC end
   ...
}

PeriodicReset ::= SEQUENCE {
   sdpID                        [1] NodeID,
   cdrID                        [2] RecordSequenceNumberString,
   timeStamp                    [3] TimeStamp,
   accountNumber                [4] NumberString,
   currencyType                 [5] CurrencyType,
   lastRecord                   [6] BOOLEAN OPTIONAL,
   periodicResetID              [7] PeriodicResetID,
   periodicResetDate            [8] Date OPTIONAL,
   balanceAtStartOfNewPeriod    [9] MoneyAmount OPTIONAL,
   balanceBeforeAdjustment      [10] MoneyAmount OPTIONAL,
   oldServiceClass              [11] ServiceClass OPTIONAL,
   serviceClassId               [12] ServiceClass,
   periodOffset                 [13] INTEGER OPTIONAL,
   startDate                    [14] Date OPTIONAL,
   periodLength                 [15] INTEGER OPTIONAL,
   typeOfPeriod                 [16] PeriodType OPTIONAL,
   -- PC
   aggrBalAtStartOfNewPeriod    [17] MoneyAmount OPTIONAL,
   aggrBalBeforeAdjustment      [18] MoneyAmount OPTIONAL,
   -- PC end
   ...
}

TemporaryBlock ::= SEQUENCE {
   sdpID                        [1] NodeID,
   cdrID                        [2] RecordSequenceNumberString,
   accountNumber                [3] NumberString,
   subscriberNumber             [4] NumberString,
   adjustmentTimeStamp          [5] TimeStamp,
   originNodeType               [6] NodeType OPTIONAL,
   originNodeID                 [7] IDString OPTIONAL,
   origTransactionID            [8] TransactionID OPTIONAL,
   origTransactionTimeStamp     [9] TimeStamp OPTIONAL,
   transactionType              [10] TransactionType OPTIONAL,
   transactionCode              [11] TransactionCode OPTIONAL,
   originOperatorId             [12] IDString OPTIONAL,
   temporaryBlockedStatusBefore [13] BOOLEAN OPTIONAL,
   temporaryBlockedStatusAfter  [14] BOOLEAN OPTIONAL,
   ...
}

AccountFlags ::= IA5String (SIZE (8))

AccountGroupID ::= INTEGER (0..2147483647)

AccountHomeRegion ::= INTEGER (0..999)

AccountUnitType ::= ENUMERATED {
   time                         (0),
   money                        (1),
   totalOctets                  (2),
   inputOctets                  (3),
   outputOctets                 (4),
   serviceSpecificUnits         (5),
   volume                       (6)
}

AccumulatorID ::= INTEGER (1..2147483647)

AccumulatorValue ::= INTEGER (-2147483648..2147483647)

AdjustmentAction ::= ENUMERATED {
   set                          (0),
   add                          (1),
   subtract                     (2),
   reset                        (3),
   remove                       (4),
   create                       (5)
}

AdjustmentAccumulator ::= SEQUENCE {
   accumulatorID                [0] AccumulatorID,
   accumulatorValueBefore       [1] AccumulatorValue OPTIONAL,
   accumulatorValueAfter        [2] AccumulatorValue OPTIONAL,
   accumulatorAdjustment        [3] AccumulatorValue OPTIONAL,
   action                       [4] AdjustmentAction,
   clearedAccumulatorValue      [5] AccumulatorValue OPTIONAL,
   accumulatorClearDateBefore   [6] Date OPTIONAL,
   accumulatorClearDateAfter    [7] Date OPTIONAL,
   accumulatorValueInitial      [8] AccumulatorValue OPTIONAL,
   accumulatorClearDateInitial  [9] Date OPTIONAL,
   ...
}

AdjustmentDedicatedAccount ::= SEQUENCE {
   dedicatedAccountID           [0] DedicatedAccountID,
   campaignIdentifier           [1] CampaignIdentifier OPTIONAL,
   accountValueBefore           [2] MoneyAmount OPTIONAL,
   accountValueAfter            [3] MoneyAmount OPTIONAL,
   adjustmentAmount             [4] MoneyAmount OPTIONAL,
   action                       [5] AdjustmentAction,
   accountExpiryDateBefore      [6] Date OPTIONAL,
   accountExpiryDateAfter       [7] Date OPTIONAL,
   originalAdjustmentAmount     [8] MoneyAmount OPTIONAL,
   clearedAccountValue          [9] MoneyAmount OPTIONAL,
   accountValueInitial          [10] MoneyAmount OPTIONAL,
   accountExpiryDateInitial     [11] Date OPTIONAL,
   accountCreditClearedReason   [12] Reason OPTIONAL,
   -- PC
   accountStartDateBefore       [13] Date OPTIONAL,
   accountStartDateAfter        [14] Date OPTIONAL,
   accountStartDateInitial      [15] Date OPTIONAL,
   realMoney                    [16] BOOLEAN OPTIONAL,
   offerID                      [17] OfferID OPTIONAL,
   accountUnitType              [18] AccountUnitType OPTIONAL,
   adjustmentSubDedicatedAccounts
                                [19] SEQUENCE OF
                                     AdjustmentSubDedicatedAccount
                                     OPTIONAL,
   -- PC end
   ...
}

-- PC
AdjustmentFaF ::= SEQUENCE {
   familyAndFriendsNumber       [0] NumberString,
   action                       [1] AdjustmentAction,
   familyAndFriendsIndicator    [2] FamilyAndFriendsIndicator,
   fafExpiryDateBefore          [3] Date OPTIONAL,
   fafExpiryDateAfter           [4] Date OPTIONAL,
   fafStartDateBefore           [5] Date OPTIONAL,
   fafStartDateAfter            [6] Date OPTIONAL,
   offerID                      [7] OfferID OPTIONAL,
   reason                       [8] Reason OPTIONAL,
   owner                        [9] Owner OPTIONAL,
   ...
}
-- PC end

-- PC
AdjustmentOffer ::= SEQUENCE {
   offerID                      [0] OfferID,
   action                       [1] AdjustmentAction,
   offerExpiryDateBefore        [2] Date OPTIONAL,
   offerExpiryDateAfter         [3] Date OPTIONAL,
   offerExpiryDateInitial       [4] Date OPTIONAL,
   offerStartDateBefore         [5] Date OPTIONAL,
   offerStartDateAfter          [6] Date OPTIONAL,
   offerStartDateInitial        [7] Date OPTIONAL,
   reason                       [8] Reason OPTIONAL,
   ...
}
-- PC end

AdjustmentRecordType ::= ENUMERATED {
   refillCDR                      (1),
   notDefined                     (2),
   linkageOfSubordinateSubscriber (3),
   removalOfSubordinateSubscriber (4),
   chargedEnquiry                 (5),
   chargedServiceClassChange      (6),
   notUsed                        (7),
   changedFamilyAndFriendsList    (8),
   clearedDedicatedAccount        (9),
   premiumRefill                  (10),
   provisioningUaDa               (11),
   ...
}

-- PC
AdjustmentSubDedicatedAccount ::= SEQUENCE {
   dedicatedAccountID           [0] DedicatedAccountID,
   accountValueBefore           [1] MoneyAmount OPTIONAL,
   accountValueAfter            [2] MoneyAmount OPTIONAL,
   adjustmentAmount             [3] MoneyAmount OPTIONAL,
   accountExpiryDateBefore      [4] Date OPTIONAL,
   accountExpiryDateAfter       [5] Date OPTIONAL,
   originalAdjustmentAmount     [6] MoneyAmount OPTIONAL,
   clearedAccountValue          [7] MoneyAmount OPTIONAL,
   accountValueInitial          [8] MoneyAmount OPTIONAL,
   accountExpiryDateInitial     [9] Date OPTIONAL,
   accountStartDateBefore       [10] Date OPTIONAL,
   accountStartDateAfter        [11] Date OPTIONAL,
   accountStartDateInitial      [12] Date OPTIONAL,
   mergedIntoDedicatedAccountID [13] DedicatedAccountID OPTIONAL,
   ...
}
-- PC end

-- PC
AggregatedBalanceDedicatedAccount ::= SEQUENCE {
    dedicatedAccountID          [0] DedicatedAccountID,
    campaignIdentifier          [1] CampaignIdentifier OPTIONAL,
    accountValueBefore          [2] MoneyAmount,
    accountValueAfter           [3] MoneyAmount,
    accountDeductedAmount       [4] MoneyAmount OPTIONAL,
    offerID                     [5] OfferID OPTIONAL,
    aggregatedBalanceSubDedicatedAccounts  
                                [6] SEQUENCE OF 
                                    AggregatedBalanceSubDedicatedAccount
                                    OPTIONAL,
    ... 
}  

-- PC end

-- PC
AggregatedBalanceSubDedicatedAccount::= SEQUENCE {
    dedicatedAccountID           [0] DedicatedAccountID,
    accountValueBefore           [1] MoneyAmount,
    accountValueAfter            [2] MoneyAmount,
    accountDeductedAmount        [3] MoneyAmount OPTIONAL,
    ...
}
-- PC end

BonusAccumulator ::= SEQUENCE {
   accumulatorID                [0] AccumulatorID,
   accumulatorValueBefore       [1] AccumulatorValue,
   accumulatorValueAfter        [2] AccumulatorValue,
   accumulatorDelta             [3] AccumulatorValue,
   ...
}

BonusDedicatedAccount ::= SEQUENCE {
   dedicatedAccountID           [0] DedicatedAccountID,
   campaignIdentifier           [1] CampaignIdentifier OPTIONAL,
   accountValueBefore           [2] MoneyAmount,
   accountValueAfter            [3] MoneyAmount,
   bonusAmount                  [4] MoneyAmount,
   accountExpiryDateBefore      [5] Date OPTIONAL,
   accountExpiryDateAfter       [6] Date OPTIONAL,
   ...
}

CampaignIdentifier ::= INTEGER (1..99999999)

CategoryValue ::= INTEGER (0..999)

CategorizationInformation ::= SEQUENCE {
   categoryType1                [1] CategoryValue OPTIONAL,
   categoryType2                [2] CategoryValue OPTIONAL,
   categoryType3                [3] CategoryValue OPTIONAL,
   categoryType4                [4] CategoryValue OPTIONAL,
   ...
}

CDRProcAccumulator ::= SEQUENCE {
   accumulatorID                [0] AccumulatorID,
   accumulatorValueBefore       [1] AccumulatorValue OPTIONAL,
   accumulatorValueAfter        [2] AccumulatorValue OPTIONAL,
   accumulatorDelta             [3] AccumulatorValue OPTIONAL,
   ...
}

CDRProcDedicatedAccount ::= SEQUENCE {
   dedicatedAccountID           [0] DedicatedAccountID,
   campaignIdentifier           [1] CampaignIdentifier OPTIONAL,
   accountValueBefore           [2] MoneyAmount,
   accountValueAfter            [3] MoneyAmount,
   chargedAmount                [4] MoneyAmount,
   ...
}

ChargingSuccessCode ::= ENUMERATED {
   chargingSucceeded                  (0),
   chargingPerformedAtDifferentCost   (1),
   chargingPerformedPresentedCostLost (2),
   chargingPerformedPartialDeduction  (3),
   chargingFailed                     (4)
}

ClearedAccumulator ::= SEQUENCE {
   accumulatorID                [0] AccumulatorID,
   clearedAccumulatorValue      [1] AccumulatorValue,
   ...
}

ClearedDedicatedAccount ::= SEQUENCE {
   dedicatedAccountID           [0] DedicatedAccountID,
   campaignIdentifier           [1] CampaignIdentifier OPTIONAL,
   clearedAccountValue          [2] MoneyAmount,
   accountCreditClearedReason   [3] Reason OPTIONAL,
   -- PC
   accountExpiryDate            [4] Date OPTIONAL,
   accountStartDate             [5] Date OPTIONAL,
   realMoney                    [6] BOOLEAN OPTIONAL,
   offerID                      [7] OfferID OPTIONAL,
   accountUnitType              [8] AccountUnitType OPTIONAL,
   clearedSubDedicatedAccounts  [9] SEQUENCE OF
                                    ClearedSubDedicatedAccount
                                    OPTIONAL,
   -- PC end
   ...
}

-- PC
ClearedSubDedicatedAccount ::= SEQUENCE {
   dedicatedAccountID           [0] DedicatedAccountID,
   clearedAccountValue          [1] MoneyAmount,
   accountCreditClearedReason   [2] Reason OPTIONAL,
   accountExpiryDate            [3] Date OPTIONAL,
   accountStartDate             [4] Date OPTIONAL,
   ...
}
-- PC end

CommunityID ::= INTEGER (0..9999999)
-- 0        Undefined
-- 1 - 9999999  CommunityID

CounterDelta ::= INTEGER (-127..127)

CounterValue ::= INTEGER (0..127)

CurrencyType ::= INTEGER {local(0), euro(1)}

Date ::= IA5String (SIZE (8))

DedicatedAccountID ::= INTEGER (1..2147483647)

DisconnectionCode ::= INTEGER (0..255)
-- 0        Service expired
-- 1 - 255  Operator defined

Duration ::= INTEGER (0..99999)

FamilyAndFriendsAction ::= ENUMERATED {
   set                                (0),
   add                                (1),
   delete                             (2)
}

FamilyAndFriendsIndicator ::= INTEGER (1..65535)

IDString ::= IA5String (SIZE (1..255))

IndividualPriceFactorHistory ::= SEQUENCE
{   
    individualPriceFactor  [0] Percent,
    units                  [1] ServiceUnits,
    ...
}
Integer32 ::= INTEGER (-2147483648..2147483647)
Integer64 ::= INTEGER
                (-9223372036854775808..9223372036854775807)

Language ::= INTEGER (1..4)

LifeCycleInformation ::= SEQUENCE 
{
   supervisionExpDateBefore    [0] Date OPTIONAL,
   supervisionExpDateAfter     [1] Date OPTIONAL,
   creditClearancePeriodBefore [2] Period OPTIONAL,
   creditClearancePeriodAfter  [3] Period OPTIONAL,
   servFeeExpDateBefore        [4] Date OPTIONAL,
   servFeeExpDateAfter         [5] Date OPTIONAL,
   serviceRemovalPeriodBefore  [6] Period OPTIONAL,
   serviceRemovalPeriodAfter   [7] Period OPTIONAL,
   accountFlagsBefore          [8] AccountFlags OPTIONAL,
   accountFlagsAfter           [9] AccountFlags OPTIONAL,
   ...
}

MonetaryUnits ::= SEQUENCE 
{
  amount       [0] Integer64,
  decimals     [1] Integer32,
  currency     [2] Unsigned32
}
MoneyAmount ::= IA5String (SIZE (1..17))

NodeID ::= IA5String (SIZE (1..20))

NodeType ::= IA5String (SIZE (1..8))

NumberString ::= IA5String (SIZE (1..30))

OfferID ::= INTEGER (1..2147483647)

Owner ::= ENUMERATED {
   subscriber                         (1),
   account                            (2)
}

Percent ::= IA5String (SIZE (1..10))

Period ::= INTEGER (0..1023)

PeriodicResetID ::= INTEGER (0..255)

PeriodType ::= INTEGER {day(0), month(1)}

PreActReasonCode ::= ENUMERATED {
   origInsideHPLMN                    (0),
   origOutsideHPLMNwithCAPv1          (1), 
   origOutsideHPLMNwithCAPv2          (2), 
   uSSDCallBack                       (3), 
   origOutsideHPLMNwithCAPv3          (4),
   firstIVRcall                       (5),
   firstUSSDaccess                    (6),
   firstExpiryDateSet                 (7)
}

PromotionPlan ::= IA5String (SIZE (1..4))

RatedDurations ::= SEQUENCE {
   debitDuration                [0] Duration OPTIONAL,
   creditDuration               [1] Duration OPTIONAL,
   freeDuration                 [2] Duration OPTIONAL,
   ...
}

Reason ::= ENUMERATED {
   serviceClassChange                 (1),
   subscriberDeleted                  (2),
   creditClearancePeriodExpired       (3),
   dedicatedAccountExpired            (4),
   other                              (5),
   -- PC
   subDedicatedAccountExpired         (6),
   offerExpired                       (7),
   fafExpired                         (8),
   -- PC end
   ...
}

RecordSequenceNumberString ::= IA5String (SIZE (1..20))

RecordType ::= ENUMERATED {
   mobileOriginating                  (1),
   mobileTerminating                  (2),
   callForwarding                     (3),
   mobileOriginatingSMSinSMSC         (4),
   mobileTerminatingSMSinSMSC         (5),
   gprsCDR                            (6),
   mobileOriginatingSMSinGPRS         (7),
   mobileTerminatingSMSinGPRS         (8),
   chargeEventCDR                     (10)
}

RelatedNumberString ::= IA5String (SIZE (0..63))

-- PC
RemovedFaF ::= SEQUENCE {
    familyAndFriendsNumber       [0] NumberString,
    familyAndFriendsIndicator    [1] FamilyAndFriendsIndicator,
    fafExpiryDate                [2] Date OPTIONAL,
    fafStartDate                 [3] Date OPTIONAL,
    offerID                      [4] OfferID OPTIONAL,
    reason                       [5] Reason OPTIONAL,
    owner                        [6] Owner OPTIONAL,
    ... 
} 
-- PC end

-- PC
RemovedOffer ::= SEQUENCE 
{
    offerID                      [0] OfferID,
    offerExpiryDate              [1] Date OPTIONAL,
    offerStartDate               [2] Date OPTIONAL,
    reason                       [3] Reason OPTIONAL,
    ...
}
-- PC end

ReplenishmentID ::= INTEGER (0..255)

SelectedCommunityIndicator ::= INTEGER (0..9999999)

ServFeeDeductSuccessCode ::= ENUMERATED {
   ok                                       (1),
   okServiceExpired                         (2),
   okServiceClassChange                     (3),
   okNoAction                               (4),
   nokServiceClassChange                    (5),
   okFirstDeductionSuppressed               (6),
   okServiceDeactivated                     (7),
   serviceFeeTypeDisconnectedDebtCleared    (8),
   partialDeductionWhenAccumulatedDeduction (9)
}

ServiceClass ::= INTEGER (0..9999)

ServiceFeeType ::= IA5String (SIZE (1..10))

ServiceOfferings ::= INTEGER (0..2147483647)

ServiceUnits ::= SEQUENCE
{
    timeUnit            [1] Unsigned32 OPTIONAL,
    moneyUnit           [2] MonetaryUnits OPTIONAL,
    totalOctetsUnit     [3] Unsigned64 OPTIONAL,
    uplinkOctetsUnit    [4] Unsigned64 OPTIONAL,
    downlinkOctetsUnit  [5] Unsigned64 OPTIONAL,
    serviceSpecificUnit [6] Unsigned64 OPTIONAL,
    ...
}
SubscriberNumberString ::= IA5String (SIZE (0..30))

TimeStamp ::= IA5String (SIZE (19))

TransactionCode ::= IA5String (SIZE (1..30))

TransactionID ::= IA5String (SIZE (1..20))

TransactionType ::= IA5String (SIZE (1..30))

Unsigned32 ::= INTEGER (0..4294967295)
Unsigned64 ::= INTEGER (0..18446744073709551615)

END
