-- ASN.1 Formal Description
CreditControlDataTypes {iso(1) member-body(2) bsi(826) disc(0)
ericsson(1249) mobileDomain (0) charging (5)
creditControlDataTypes (1) asn1Module (0)}
DEFINITIONS IMPLICIT TAGS ::=
BEGIN
EXPORTS SDPCreditControlRecord, UsedServiceUnits;
---------------------------------------------------------------
--
-- CREDIT CONTROL RECORD
--
---------------------------------------------------------------
SDPCreditControlRecord ::= CHOICE
{
	creditControlRecord [0] CreditControlRecord,
	...
}
CreditControlRecord ::= SEQUENCE
{
	serviceIdentifier [1] Unsigned32,
	usedServiceUnits [2] UsedServiceUnits OPTIONAL,
	eventTime [3] TimeStamp,
	triggerTime [4] TimeStamp,
	serviceScenario [5] ServiceScenario,
	serviceExtension [6] ServiceExtension OPTIONAL,
	roamingPosition [7] RoamingPosition OPTIONAL,
	tariffInfo [8] SEQUENCE OF SelectionTreeParameter OPTIONAL,
	cCAccountData [9] CCAccountData,
	chargingContextSpecific [10] SEQUENCE OF ContextParameter OPTIONAL,
	treeDefinedFields [11] SEQUENCE OF TreeDefinedField OPTIONAL,
	bonusAdjustment [12] BonusAdjustment OPTIONAL,
	serviceSetupResult [13] ServiceSetupResult OPTIONAL,
	terminationCause [14] TerminationCause OPTIONAL,
	ratedUnits [15] RatedUnits OPTIONAL,
	individualPriceFactorHistory [16] SEQUENCE OF IndividualPriceFactorHistory OPTIONAL,
	...
}
--------------------------------------------------------------
--
-- CREDIT CONTROL DATA TYPES
--
--------------------------------------------------------------
AccountFlags ::= IA5String (SIZE (8))
AccountGroupID ::= INTEGER (0..2147483647)
AccountUnitType ::= ENUMERATED {
	time(0),
	money(1),
	totalOctets(2),
	inputOctets(3),
	outputOctets(4),
	serviceSpecificUnits(5),
	volume(6),
	...
}
Accumulator ::= SEQUENCE
{
	accumulatorID [0] AccumulatorID,
	accumulatorBefore [1] Integer32 OPTIONAL,
	accumulatorChange [2] Integer32,
	accumulatorAfter [3] Integer32,
	accumulatorBeforeSession [4] Integer32 OPTIONAL,
	...
}
AccumulatorID ::= INTEGER (1..2147483647)
Accumulators ::= SEQUENCE (SIZE (1..255)) OF Accumulator
AddressString ::= OCTET STRING (SIZE (1..20))
BonusAdjustment ::= SEQUENCE
{
	accountValueBefore [0] MonetaryUnits OPTIONAL,
	accountValueAfter [1] MonetaryUnits OPTIONAL,
	bonusAmount [2] MonetaryUnits OPTIONAL,
	accumulators [3] Accumulators OPTIONAL,
	dedicatedAccounts [4] DedicatedAccounts OPTIONAL,
	lifeCycleInformation [5] LifeCycleInformation OPTIONAL,
	-- PC
	aggregatedValueBefore [6] MonetaryUnits OPTIONAL,
	aggregatedValueAfter [7] MonetaryUnits OPTIONAL,
	-- end PC
	...
}
CCAccountData ::= SEQUENCE
{
	servedAccount [0] AddressString,
	serviceClassID [1] ServiceClassID,
	accountGroupID [2] AccountGroupID,
	accountValueBefore [3] MonetaryUnits OPTIONAL,
	accountValueAfter [4] MonetaryUnits OPTIONAL,
	communityInformation [5] CommunityInformation OPTIONAL,
	accumulators [6] Accumulators OPTIONAL,
	dedicatedAccounts [7] DedicatedAccounts OPTIONAL,
	familyAndFriendsID [8] FamilyAndFriendsID OPTIONAL,
	familyAndFriendsNo [9] AddressString OPTIONAL,
	serviceOfferings [10] Unsigned32,
	accumulatedCost [11] MonetaryUnits OPTIONAL,
	accountValueUsed [12] MonetaryUnits OPTIONAL,
	accountValueDeducted [13] MonetaryUnits,
	-- PC
	aggregatedValueBefore [14] MonetaryUnits OPTIONAL,
	aggregatedValueAfter [15] MonetaryUnits OPTIONAL,
	accumulatedUnits [16] Integer64 OPTIONAL,
	accountUnitsUsed [17] Integer64 OPTIONAL,
	accountUnitsDeducted [18] Integer64 OPTIONAL,
	-- end PC
	...
}
CommunityID ::= INTEGER (1..9999999)
CommunityIDs ::= SEQUENCE
{
	communityID1 [0] CommunityID OPTIONAL,
	communityID2 [1] CommunityID OPTIONAL,
	communityID3 [2] CommunityID OPTIONAL,
	...
}
CommunityInformation ::= SEQUENCE
{
	selectedCommunityID [0] CommunityID OPTIONAL,
	servedCommunityIDs [1] CommunityIDs OPTIONAL,
	nonServedCommunityIDs [2] CommunityIDs OPTIONAL,
	nonServedCommunityIDNA [3] BOOLEAN OPTIONAL,
	nonServedCommunityNo [4] AddressString OPTIONAL,
	...
}
ContextParameter ::= SEQUENCE
{
	parameterID [0] Integer64,
	parameterValue [1] ContextParameterValueType
}
ContextParameterValueType ::= CHOICE
{
	boolean [0] BOOLEAN,
	integer32 [1] Integer32,
	integer64 [2] Integer64,
	unsigned32 [3] Unsigned32,
	unsigned64 [4] Unsigned64,
	addressString [5] AddressString,
	octetString [6] OCTET STRING,
	string [7] UTF8String,
	time [8] Time,
	partyInformation [9] PartyInformation,
	...
}
Date ::= IA5String (SIZE (8))
DedicatedAccount ::= SEQUENCE
{
	dedicatedAccountID [0] DedicatedAccountID,
	dedicatedAccountValueBefore [1] MonetaryUnits OPTIONAL,
	dedicatedAccountValueAfter [2] MonetaryUnits OPTIONAL,
	dedicatedAccountChange [3] MonetaryUnits OPTIONAL,
	dedicatedAccountCampaignID [4] DedicatedAccountCampaignID OPTIONAL,
	accountExpiryDateBefore [5] Date OPTIONAL,
	accountExpiryDateAfter [6] Date OPTIONAL,
	-- PC
	accountStartDateBefore [7] Date OPTIONAL,
	accountStartDateAfter [8] Date OPTIONAL,
	realMoney [9] BOOLEAN OPTIONAL,
	offerID [10] OfferID OPTIONAL,
	dedicatedAccountUnitsBefore [11] Unsigned64 OPTIONAL,
	dedicatedAccountUnitsAfter [12] Unsigned64 OPTIONAL,
	dedicatedAccountUnitsChange [13] Integer64 OPTIONAL,
	accountUnitType [14] AccountUnitType OPTIONAL,
	subDedicatedAccounts [15] SubDedicatedAccounts OPTIONAL,
	-- end PC
	...
}
DedicatedAccountID ::= INTEGER (1..2147483647)
DedicatedAccountCampaignID ::= INTEGER (0..99999999)
DedicatedAccounts ::= SEQUENCE (SIZE (1..255)) OF DedicatedAccount
FamilyAndFriendsID ::= INTEGER (1..65535)
IndividualPriceFactorHistory ::= SEQUENCE
{
	individualPriceFactor [0] Percent,
	units [1] ServiceUnits,
	...
}
Integer32 ::= INTEGER (-2147483648..2147483647)
Integer64 ::= INTEGER (-9223372036854775808..9223372036854775807)
LifeCycleInformation ::= SEQUENCE
{
	supervisionExpDateBefore [0] Date OPTIONAL,
	supervisionExpDateAfter [1] Date OPTIONAL,
	creditClearancePeriodBefore [2] Period OPTIONAL,
	creditClearancePeriodAfter [3] Period OPTIONAL,
	servFeeExpDateBefore [4] Date OPTIONAL,
	servFeeExpDateAfter [5] Date OPTIONAL,
	serviceRemovalPeriodBefore [6] Period OPTIONAL,
	serviceRemovalPeriodAfter [7] Period OPTIONAL,
	accountFlagsBefore [8] AccountFlags OPTIONAL,
	accountFlagsAfter [9] AccountFlags OPTIONAL,
	...
}
MonetaryUnits ::= SEQUENCE
{
	amount [0] Integer64,
	decimals [1] Integer32,
	currency [2] Unsigned32
}
OfferID ::= INTEGER (1..2147483647)
PartyInformation ::= CHOICE
{
	msisdn [0] AddressString,
	imsi [1] AddressString,
	sipUri [2] UTF8String,
	nai [3] UTF8String,
	...
}
Percent ::= IA5String (SIZE (1..10))
Period ::= INTEGER (0..1023)
RatedUnits ::= SEQUENCE
{
	debitUnits [0] RatedUnitsValues OPTIONAL,
	creditUnits [1] RatedUnitsValues OPTIONAL,
	freeUnits [2] RatedUnitsValues OPTIONAL,
	...
}
RatedUnitsValues ::= SEQUENCE
{
	ratedTimeUnits [0] Unsigned32 OPTIONAL,
	ratedTotalOctetsUnits [1] Unsigned64 OPTIONAL,
	ratedUplinkOctetsUnits [2] Unsigned64 OPTIONAL,
	ratedDownlinkOctetsUnits [3] Unsigned64 OPTIONAL,
	ratedServiceSpecificUnits [4] Unsigned64 OPTIONAL,
	...
}
RoamingPosition ::= ENUMERATED
{
	insideHPLMN(0),
	outsideHPLMN(1),
	...
}
SelectionTreeParameter ::= SEQUENCE
{
	selectionTreeID [0] UTF8String,
	selectionTreeVersion [1] UTF8String,
	selectionTreeType [2] SelectionTreeType,
	...
}
SelectionTreeType ::= ENUMERATED
{
	rating(0),
	bonus(1),
	selection(2),
	dedicatedAccount(3),
	communityCharging(4),
	numberNormalization(5),
	ussdTextMessage(6),
	accountManagement(7),
	preAnalysis(8),
	...
}
ServiceClassID ::= INTEGER (0..9999)
ServiceExtension ::= ENUMERATED
{
	ussdCallback(0),
	capV1Roaming(1),
	...
}
ServiceSetupResult ::= ENUMERATED
{
	successfulReleasedByService(0),
	successfulDisconnectedByCallingParty(1),
	successfulDisconnectByCalledParty(2),
	successfulTollfree(3),
	nonSuccessfulCalledPartyRouteSelectFailure(4),
	nonSuccessfulCalledPartyBusy(5),
	nonSuccessfulCalledPartyNotReachable(6),
	nonSuccessfulCalledPartyNoAnswer(7),
	nonSuccessfulCallingPartyAbandon(8),
	nonSuccessfulOtherReason(14),
	callForwardingChargingCancelled(15),
	...
}
ServiceScenario ::= ENUMERATED
{
	mobileOriginating(0),
	mobileForwarding(1),
	mobileTerminating(2),
	...
}
ServiceUnits ::= SEQUENCE
{
	timeUnit [1] Unsigned32 OPTIONAL,
	moneyUnit [2] MonetaryUnits OPTIONAL,
	totalOctetsUnit [3] Unsigned64 OPTIONAL,
	uplinkOctetsUnit [4] Unsigned64 OPTIONAL,
	downlinkOctetsUnit [5] Unsigned64 OPTIONAL,
	serviceSpecificUnit [6] Unsigned64 OPTIONAL,
	...
}
SubDedicatedAccount ::= SEQUENCE
{
	dedicatedAccountID [0] DedicatedAccountID,
	dedicatedAccountValueBefore [1] MonetaryUnits OPTIONAL,
	dedicatedAccountValueAfter [2] MonetaryUnits OPTIONAL,
	dedicatedAccountChange [3] MonetaryUnits OPTIONAL,
	accountExpiryDateAfter [4] Date OPTIONAL,
	accountStartDateAfter [5] Date OPTIONAL,
	dedicatedAccountUnitsBefore [6] Unsigned64 OPTIONAL,
	dedicatedAccountUnitsAfter [7] Unsigned64 OPTIONAL,
	dedicatedAccountUnitsChange [8] Integer64 OPTIONAL,
	...
}
SubDedicatedAccounts ::= SEQUENCE OF SubDedicatedAccount
TariffChangeUsage ::= ENUMERATED
{
	before(0),
	after(1),
	indeterminate(2)
}
TerminationCause ::= ENUMERATED
{
	diameterLogout(1),
	diameterServiceNotProvided(2),
	diameterBadAnswer(3),
	diameterAdministrative(4),
	diameterLinkBroken(5),
	diameterAuthExpired(6),
	diameterUserMoved(7),
	diameterSessionTimeout(8),
	...
}
Time ::= SEQUENCE
{
	sec [0] Integer32,
	tz [1] INTEGER(-128..127)
}
TimeStamp ::= IA5String (SIZE(19))
TreeDefinedField ::= SEQUENCE
{
	parameterID [0] UTF8String,
	parameterValue [1] TreeDefinedFieldType
}
TreeDefinedFieldType ::= CHOICE
{
	boolean [0] BOOLEAN,
	integer64 [2] Integer64,
	string [7] UTF8String,
	...
}
Unsigned32 ::= INTEGER (0..4294967295)
Unsigned64 ::= INTEGER (0..18446744073709551615)
UsedServiceUnits ::= SEQUENCE (SIZE (1..3)) OF
UsedServiceUnit
UsedServiceUnit ::= SEQUENCE
{
	tariffChangeUsage [0] TariffChangeUsage OPTIONAL,
	timeUnit [1] Unsigned32 OPTIONAL,
	moneyUnit [2] MonetaryUnits OPTIONAL,
	totalOctetsUnit [3] Unsigned64 OPTIONAL,
	uplinkOctetsUnit [4] Unsigned64 OPTIONAL,
	downlinkOctetsUnit [5] Unsigned64 OPTIONAL,
	serviceSpecificUnit [6] Unsigned64 OPTIONAL,
	...
}
END
